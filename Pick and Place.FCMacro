from PySide.QtGui import *
from PySide.QtCore import *
import json


arr = []
j    = 0
class ViewObserver:
	def __init__(self, view):
		self.view = view
   
	def logPosition(self, info):
		down = (info["State"] == "DOWN")
		pos = info["Position"]

		global arr
		global j
		
		f = open("C:/Users/bini/Desktop/JSON/mouse.txt",mode='w',encoding='utf-8')
		if (down):
			
			#FreeCAD.Console.PrintMessage("Clicked on position: ("+str(pos[0])+", "+str(pos[1])+")\n")
			pnt = self.view.getPoint(pos)
		
			#FreeCAD.Console.PrintMessage("World coordinates: " + str(pnt) + "\n")
			info = self.view.getObjectInfo(pos)
			#FreeCAD.Console.PrintMessage(" Object info: " + str(info) + "\n")
			result = list(info.items())
			
	
			for i in range(0,3):
				b = result[i]
				f.write(str(b[1]) + '\n')
				arr.append(b[1])
			j = j+1
			if (j == 2):
				arr = []
				j = 0
			
			FreeCAD.Console.PrintMessage("counter of mouseclick = " + str(j) + "\n")
			FreeCAD.Console.PrintMessage("Append Array Distance" + str(arr) + "\n")
			f.close()
			
       
class GetInform:

	def __init__(self):
    		pass
	def coordinates(self):
    		#FreeCAD.Console.PrintMessage("I m inside mouseclick method")
		return arr









class placeOperation(QWidget):
	def __init__(self):
		
		super(placeOperation, self).__init__()  
		self.setWindowFlags(Qt.WindowStaysOnTopHint)
		self.setWindowTitle("Pick and Place Operation")
		
		self.btnPlace = QPushButton("Mark at position")
		self.btnPlace.clicked.connect(self.doWorkPlace)

		self.btnDoPlace = QPushButton("GetPos")
		self.btnDoPlace.clicked.connect(self.getPose)

		self.btnDoJson = QPushButton("Generate JSON")
		self.btnDoJson.clicked.connect(self.Import2Jason)

		self.lableX = QLabel("Position at X")
		self.lableY = QLabel("Position at Y")
		self.lableZ = QLabel("Position at Z")
		

		self.box1 = QDoubleSpinBox()
		self.box1.setMinimum(-1000)
		self.box1.setMaximum(1000)
		self.box1.setSingleStep(0.5)
		self.box1.setSuffix('mm')


		self.box2 = QDoubleSpinBox()
		self.box2.setMinimum(-1000)
		self.box2.setMaximum(1000)
		self.box2.setSingleStep(0.5)
		self.box2.setSuffix('mm')

		self.box3= QDoubleSpinBox()
		self.box3.setSuffix('mm')
		self.box3.setMinimum(-1000)
		self.box3.setMaximum(1000)
		self.box3.setSingleStep(0.5)
		self.box3.setSuffix('mm')

		layout =QHBoxLayout()
		layout.addWidget(self.lableX)
		layout.addWidget(self.box1)
		layout.addWidget(self.lableY)
		layout.addWidget(self.box2)
		layout.addWidget(self.lableZ)
		layout.addWidget(self.box3)
		layout.addWidget(self.btnDoPlace)
		layout.addWidget(self.btnPlace)
		layout.addWidget(self.btnDoJson)
		

		
		
		
		self.setLayout(layout)
		self.show()
		v = FreeCADGui.activeDocument().activeView()
		o = ViewObserver(v)
		c = v.addEventCallback("SoMouseButtonEvent",o.logPosition)	

		
	def getPose(self):

		o = GetInform()
		#FreeCAD.Console.PrintMessage("Where is the information" + "\n")

		obj1 = o. coordinates()
		FreeCAD.Console.PrintMessage('Postion retrived')
		FreeCAD.Console.PrintMessage(str(obj1))

					
		self.box1.setValue(obj1[0])
		self.box2.setValue(obj1[1])
		self.box3.setValue(obj1[2])
	
	def doWorkPlace(self):
		
		
		Gui.activateWorkbench("SketcherWorkbench")

		Gui.getDocument('NewDesign').ActiveView.setActiveObject('pdbody',App.getDocument('NewDesign').getObject('Body'),'')
		
		App.getDocument('NewDesign').getObject('Body').newObject('Sketcher::SketchObject','Sketch002')
		App.getDocument('NewDesign').getObject('Sketch002').Support = (App.getDocument('NewDesign').getObject('DatumPlane'),[''])
		App.getDocument('NewDesign').getObject('Sketch002').MapMode = 'FlatFace'
		App.ActiveDocument.recompute()
		Gui.getDocument('NewDesign').setEdit(App.getDocument('NewDesign').getObject('Body'),0,'Sketch002.')

		o = GetInform()
		obj2 = o.coordinates()
		x = float(obj2[0])
		y = float(obj2[1])

		diameter = 5
		FreeCAD.Console.PrintMessage(str(diameter))
		App.getDocument('NewDesign').getObject('Sketch002').addGeometry(Part.Circle(App.Vector(-x, y, 0), App.Vector(0,0,1), diameter), False)
		App.ActiveDocument.recompute()
		App.getDocument('NewDesign').recompute()

		
		Gui.getDocument('NewDesign').resetEdit()

	def Import2Jason(self):
		
		x = self.box1.text()
		y = self.box2.text()
		z = self.box3.text()
		
		# angle of drill to the object
		ax = 0
		ay = 0
		az = 0

	    
		
		f = open("C:/Users/bini/Desktop/JSON/placePosition.JSON",mode='w',encoding='utf-8')
		# a Python object (dictionary):
		persingObject = {
		    "Name" : "placeLocation",
		    #"globalId": "ss",
		    "Type" : "Location",
		    "LocationID" : "00",
		    "X": x,
		    "Y": y,
		    "Z": z,
		    "RX": ax,
		    "RY": ay,
		    "RZ": az
		}
		# convert into JSON:
		y = json.dumps(persingObject, indent = 4)
		f.write(y)
		
		
		
		f.close()
		FreeCAD.Console.PrintMessage("The JSON file is created")




newNails = placeOperation()
