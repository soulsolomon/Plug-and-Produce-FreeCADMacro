from PySide.QtGui import *
from PySide.QtCore import *
import FreeCAD as App
import FreeCADGui


arr = []
j    = 0
class ViewObserver:
	def __init__(self, view):
		self.view = view
   
	def logPosition(self, info):
		down = (info["State"] == "DOWN")
		pos = info["Position"]

		global arr
		global j
		
		f = open("C:/Users/bini/Desktop/JSON/mouse.txt",mode='w',encoding='utf-8')
		if (down):
			
			#FreeCAD.Console.PrintMessage("Clicked on position: ("+str(pos[0])+", "+str(pos[1])+")\n")
			pnt = self.view.getPoint(pos)
		
			#FreeCAD.Console.PrintMessage("World coordinates: " + str(pnt) + "\n")
			info = self.view.getObjectInfo(pos)
			#FreeCAD.Console.PrintMessage(" Object info: " + str(info) + "\n")
			result = list(info.items())
			
	
			for i in range(0,3):
				b = result[i]
				f.write(str(b[1]) + '\n')
				arr.append(b[1])
			j = j+1
			if (j == 3):
				arr = []
				j = 0
			
			FreeCAD.Console.PrintMessage("counter of mouseclick = " + str(j) + "\n")
			FreeCAD.Console.PrintMessage("Append Array Distance" + str(arr) + "\n")
			f.close()
			
       
class GetInform:

	def __init__(self):
    		pass
	def coordinates(self):
    		#FreeCAD.Console.PrintMessage("I m inside mouseclick method")
		return arr






class NailingOperation(QWidget):
	def __init__(self):
		
		super(NailingOperation, self).__init__()  
		self.setWindowFlags(Qt.WindowStaysOnTopHint)
		self.setWindowTitle("Nailing")
		

		self.btnDoWork = QPushButton("Create Nail at Position")
		self.btnDoWork.clicked.connect(self.doWork)
		self.btnDoJson = QPushButton("Generate JSON")
		self.btnPose = QPushButton("Get Position")
		self.btnPose.clicked.connect(self.getPose)

		self.lableX = QLabel("Start position at X")
		self.lableY = QLabel("Start position at Y")
		self.lableZ = QLabel("Start position at Z")
		self.labelD = QLabel("Distance")
		self.labelId = QLabel("Drill ID")
		self.labelAmount = QLabel("Amount")
		self.lableXE = QLabel("End position at X")
		self.lableYE = QLabel("End position at Y")
		self.lableZE = QLabel("End position at Z")



		self.box1 = QDoubleSpinBox()
		self.box1.setSuffix('mm')
		self.box1.setMinimum(-1000)
		self.box1.setMaximum(1000)

		self.box2 = QDoubleSpinBox()
		self.box2.setSuffix('mm')
		self.box2.setMinimum(-1000)
		self.box2.setMaximum(1000)

		self.box3= QDoubleSpinBox()
		self.box3.setSuffix('mm')
		self.box3.setMinimum(-1000)
		self.box3.setMaximum(1000)
					
		self.box4= QDoubleSpinBox()
		self.box4.setSuffix('mm')
		self.box4.setMinimum(-1000)
		self.box4.setMaximum(1000)
		self.box5= QDoubleSpinBox()
		self.box5.setSuffix('')

		self.box6 = QDoubleSpinBox()
		self.box6.setSuffix('mm')
		self.box6.setMinimum(-1000)
		self.box6.setMaximum(1000)

		self.box7 = QDoubleSpinBox()
		self.box7.setSuffix('mm')
		self.box7.setMinimum(-1000)
		self.box7.setMaximum(1000)

		self.box8= QDoubleSpinBox()
		self.box8.setSuffix('mm')
		self.box8.setMinimum(-1000)
		self.box8.setMaximum(1000)	

		self.box9 = QDoubleSpinBox() #amount of nails
		self.box9.setSuffix('')

		layout =QGridLayout()
		layout.addWidget(self.lableX, 0, 0)
		layout.addWidget(self.box1, 0, 1)
		layout.addWidget(self.lableY, 1, 0)
		layout.addWidget(self.box2, 1, 1)
		layout.addWidget(self.lableZ, 2, 0)
		layout.addWidget(self.box3, 2, 1)

		layout.addWidget(self.lableXE, 0, 2)
		layout.addWidget(self.box6, 0, 3)
		layout.addWidget(self.lableYE, 1, 2)
		layout.addWidget(self.box7, 1, 3)
		layout.addWidget(self.lableZE, 2, 2)
		layout.addWidget(self.box8, 2, 3)

		layout.addWidget(self.labelD,0, 4)
		layout.addWidget(self.box4, 0, 5)

		layout.addWidget(self.labelId,1,4 )
		layout.addWidget(self.box5, 1,5)
		layout.addWidget(self.labelAmount, 2, 4)
		layout.addWidget(self.box9, 2, 5)

		layout.addWidget(self.btnPose, 3,0,3,2)
		layout.addWidget(self.btnDoWork, 3,2,3,2)
		layout.addWidget(self.btnDoJson,3,4,3,3)
		self.setLayout(layout)
		self.show()


		v = FreeCADGui.activeDocument().activeView()
		o = ViewObserver(v)
		c = v.addEventCallback("SoMouseButtonEvent",o.logPosition)

	def getPose(self):

		o = GetInform()
		#FreeCAD.Console.PrintMessage("Where is the information" + "\n")

		obj1 = o. coordinates()
		FreeCAD.Console.PrintMessage('Succeded until here')
		FreeCAD.Console.PrintMessage(str(obj1))

					
		self.box1.setValue(obj1[0])
		self.box2.setValue(obj1[1])
		self.box3.setValue(obj1[2])

		self.box6.setValue(obj1[3])
		self.box7.setValue(obj1[4])
		self.box8.setValue(obj1[5])
				
	def doWork(self):
		Gui.activateWorkbench("SketcherWorkbench")

		#todo		
		#creat nails from array obj[]



		#Import to JSON
		
		
		

newNails = NailingOperation()
